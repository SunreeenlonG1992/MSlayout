Attribute VB_Name = "Module1"
Sub HelloWorld()

'Dim myex As Excel.Application
'Dim mywb As Excel.Workbook
'Dim mysht As Worksheet
'
'Set myex = New Excel.Application
'myex.Visible = True
'Set mywb = myex.Workbooks.Open("C:\Users\lenovo\Downloads\111.xlsx")
'Set mysht = mywb.Worksheets(1)
'MsgBox mysht.Name




Dim objDF As MicroStationDGN.DesignFile
Dim oscan As ElementScanCriteria
Dim oenum As ElementEnumerator
Dim olevels As Levels
Dim olevel As Level
Dim ele As Element


Dim myexcel As excel.Application
Dim mywb As excel.Workbook
Dim myws As excel.Worksheet
Dim i As Integer
Dim dic As New Dictionary


i = 1

Set myexcel = New excel.Application
Set mywb = myexcel.Workbooks.Open("D:\1111\sun.xlsx")
myexcel.Visible = True
Set myws = mywb.Worksheets(1)




Set objDF = MicroStationDGN.ActiveDesignFile
Set olevels = ActiveModelReference.Levels
Set oscan = New ElementScanCriteria

oscan.ExcludeAllTypes
oscan.IncludeType msdElementTypeCellHeader

Debug.Print olevels.Count
Set oenum = ActiveModelReference.Scan(oscan)

'CadInputQueue.SendCommand "Mark"
ShowStatus "sunrenlong"
Do While oenum.MoveNext

    Set ele = oenum.Current
    Set olevel = ActiveModelReference.Levels(1)
    If ele.IsCellElement Then
      Debug.Print ele.AsCellElement.Name
            If Not dic.Exists(ele.AsCellElement.Name) Then
                   dic.Add ele.AsCellElement.Name, 1
                
            ElseIf dic.Exists(ele.AsCellElement.Name) Then
                   dic.Item(ele.AsCellElement.Name) = dic.Item(ele.AsCellElement.Name) + 1
                   'MsgBox dic.Item("Robot_KR210 R2700 extra")
            End If
            Debug.Print dic.Item(ele.AsCellElement.Name)
                
          
          
          
'      myws.Cells(i, 1).Value = ele.AsCellElement.Name
'      i = i + 1
      
'      If InStr(ele.AsCellElement.Name, "Robot_KR210 R2700 extra") Then
'      ele.Level = ActiveModelReference.Levels("电控柜及桥架")
'
'      ele.Color = 3
'      ele.Redraw
'      ele.Rewrite
'
'      End If
    End If
    
Loop
    

Dim a


For Each a In dic.Keys
    myws.Cells(i, 1).Value = a
    myws.Cells(i, 2).Value = dic(a)
    i = i + 1

Next

'myws.Columns.AutoFit
myws.Range("A:A").AutoFit


End Sub



Sub sublist()




Dim objDF As MicroStationDGN.DesignFile
Dim oscan As ElementScanCriteria
Dim oenum As ElementEnumerator
Dim olevels As Levels
Dim olevel As Level
Dim ele As Element


Dim myexcel As excel.Application
Dim mywb As excel.Workbook
Dim myws As excel.Worksheet
Dim i As Integer
i = 1
Dim dic As New Dictionary


Set myexcel = New excel.Application
Set mywb = myexcel.Workbooks.Open("D:\1111\sun.xlsx")
myexcel.Visible = True
Set myws = mywb.Worksheets(1)




Set objDF = MicroStationDGN.ActiveDesignFile
Set olevels = ActiveModelReference.Levels
Set oscan = New ElementScanCriteria

oscan.ExcludeAllTypes
oscan.IncludeType msdElementTypeCellHeader

Debug.Print olevels.Count
Set oenum = ActiveModelReference.Scan(oscan)

ShowStatus "sunrenlong"
Do While oenum.MoveNext

    Set ele = oenum.Current
    Set olevel = ActiveModelReference.Levels(1)
    If ele.IsCellElement Then
      Debug.Print ele.AsCellElement.Name
            If Not dic.Exists(ele.AsCellElement.Name) Then
                   dic.Add ele.AsCellElement.Name, 1
                
            ElseIf dic.Exists(ele.AsCellElement.Name) Then
                   dic.Item(ele.AsCellElement.Name) = dic.Item(ele.AsCellElement.Name) + 1
                   'MsgBox dic.Item("Robot_KR210 R2700 extra")
            End If
            Debug.Print dic.Item(ele.AsCellElement.Name)

    End If
    
Loop
    

Dim a


For Each a In dic.Keys
    myws.Cells(i, 1).Value = a
    myws.Cells(i, 2).Value = dic(a)
    i = i + 1

Next

'myws.Columns.AutoFit
myws.Range("A:A").AutoFit


End Sub





End Sub

Attribute VB_Name = "Module2"
 ' Function for checking the existence of a level
Private Function LevelExist(LevelName As String) As Boolean
    Dim oLv As Level
    LevelExist = False
    For Each oLv In ActiveDesignFile.Levels
        If UCase(oLv.Name) = UCase(LevelName) Then
            LevelExist = True
            Exit Function
        End If
    Next
End Function
 
Sub Texte_on_Level()
    Dim oLv As Level
    Dim neuerLevel As String
    ' Check whether the new name was given as a parameter:
    neuerLevel = KeyinArguments
     
    ' If no parameter is given, use "LevelOfText":
    If Len(Trim(newLevel)) = 0 Then
        newLevel = "LevelOfText"
    End If
     
    ' If the new level name does not exist, then create the level:
    If Not LevelExist(newLevel) Then
        ActiveDesignFile.AddNewLevel newLevel
    End If
    Set oLv = -.Levels(newLevel)
     
    ' Look for all text and move it to the new level:
    Dim Ee As ElementEnumerator
    Dim Sc As New ElementScanCriteria
    Sc.ExcludeAllTypes
    Sc.IncludeType msdElementTypeText
    Set Ee = ActiveModelReference.Scan(Sc)
    Do While Ee.MoveNext
        Set Ee.Current.Level = oLv
        Ee.Current.Rewrite
    Loop
End Sub

Attribute VB_Name = "Module3"
Public Sub getFenceElements()
   Dim oFence As Fence
   Dim oElEnum As ElementEnumerator
   Dim oEl As Element
   Set oFence = ActiveDesignFile.Fence
   If oFence.IsDefined Then
      Set oElEnum = oFence.GetContents
      oElEnum.Reset
      While oElEnum.MoveNext
         Set oEl = oElEnum.Current
         'Change the color of the element
         oEl.Color = 3
         oEl.Redraw msdDrawingModeNormal
         oEl.Rewrite
      Wend
   End If
End Sub


Public Sub getFenceElements111()
   Dim oFence As Fence
   Dim oElEnum As ElementEnumerator
   Dim oEl As Element
   
   
Dim myexcel As excel.Application
Dim mywb As excel.Workbook
Dim myws As excel.Worksheet
Dim i As Integer
Dim dic As New Dictionary
i = 1

Set myexcel = New excel.Application
Set mywb = myexcel.Workbooks.Open("D:\1111\sun.xlsx")
myexcel.Visible = True
Set myws = mywb.Worksheets(1)

   
   
   
   Set oFence = ActiveDesignFile.Fence
   If oFence.IsDefined Then
      Set oElEnum = oFence.GetContents
      oElEnum.Reset
      While oElEnum.MoveNext
      Set ele = oElEnum.Current
                            If ele.IsCellElement Then
                              Debug.Print ele.AsCellElement.Name
                                    If Not dic.Exists(ele.AsCellElement.Name) Then
                                           dic.Add ele.AsCellElement.Name, 1
                                        
                                    ElseIf dic.Exists(ele.AsCellElement.Name) Then
                                           dic.Item(ele.AsCellElement.Name) = dic.Item(ele.AsCellElement.Name) + 1
                                           'MsgBox dic.Item("Robot_KR210 R2700 extra")
                                    End If
                                    Debug.Print dic.Item(ele.AsCellElement.Name)
                        
                            End If
      Wend
   End If
   
   
Dim a


For Each a In dic.Keys
    myws.Cells(i, 1).Value = a
    myws.Cells(i, 2).Value = dic(a)
    i = i + 1
Next

myws.Range("A:A").AutoFit
   
   
   
End Sub

Attribute VB_Name = "Module4"
Public Sub getFenceElements()
   Dim oFence As Fence
   Dim oElEnum As ElementEnumerator
   Dim oEl As Element
   
   
Dim myexcel As excel.Application
Dim mywb As excel.Workbook
Dim myws As excel.Worksheet
Dim i As Integer
Dim dic As New Dictionary
i = 1
'
'Set myexcel = New Excel.Application
'Set mywb = myexcel.Workbooks.Open("D:\1111\sun.xlsx")
'myexcel.Visible = True
'Set myws = mywb.Worksheets(1)

   
   
Set objDF = MicroStationDGN.ActiveDesignFile
Set olevels = ActiveModelReference.Levels
Set oscan = New ElementScanCriteria

oscan.ExcludeAllTypes
oscan.IncludeType msdElementTypeCellHeader


Set oenum = ActiveModelReference.Scan(oscan)

Do While oenum.MoveNext

    Set ele = oenum.Current
    Dim ocell As CellElement
    
    If ele.IsCellElement Then
                Set ocell = ele.AsCellElement
                
            If Not dic.Exists(ocell.Origin.X) Then
                   dic.Add ele.AsCellElement.Name, 1
                   Debug.Print ocell.Origin.X
                
            ElseIf dic.Exists(ocell.Origin.X) Then
                   dic.Item(ele.AsCellElement.Name) = dic.Item(ele.AsCellElement.Name) + 1
                   Debug.Print ocell.Origin.X
            End If
            Debug.Print dic.Item(ele.AsCellElement.Name)

    End If
    
Loop
   
'
'Dim a
'
'
'For Each a In dic.Keys
'    myws.Cells(i, 1).Value = a
'    myws.Cells(i, 2).Value = dic(a)
'    i = i + 1
'Next
'
'myws.Range("A:A").AutoFit
'
   
   
End Sub

Attribute VB_Name = "Module5"
Sub placecell()

Dim ocell As CellElement
'Dim opoint As Point3d


Dim myexcel As excel.Application
Dim mywb As excel.Workbook
Dim myws As excel.Worksheet

Set myexcel = GetObject(, "excel.application")
Set mywb = myexcel.ActiveWorkbook
Set myws = mywb.Worksheets(1)
Debug.Print (myws.Name)


Dim lastrow As Integer
lastrow = myws.UsedRange.Rows.Count
Dim a As Double
Dim b As Double
Dim op As Point3d
Dim orotation As Matrix3d

dangle = 30 * Pi / 180
op.X = 0
op.Y = 0
op.Z = 1

For i = 2 To lastrow

orotation = Matrix3dFromVectorAndRotationAngle(op, dangle)
a = CDbl(myws.Cells(i, 2).Value)
b = CDbl(myws.Cells(i, 3).Value)
'Set ocell = CreateCellElement3("1234", Point3dFromXY(a, b), False)
Set ocell = CreateCellElement2("1234", Point3dFromXY(a, b), Point3dFromXYZ(1, 2, 1), False, orotation)
ActiveModelReference.AddElement ocell
ocell.Redraw
ocell.Rewrite
MsgBox ("ok")

Next













End Sub

Attribute VB_Name = "UserForm1"
Attribute VB_Base = "0{B0A9E95D-B2A8-4371-BF00-123F60D22916}{A44428C9-BD1A-4720-B0EA-389E136B2CE1}"
Attribute VB_GlobalNameSpace = False
Attribute VB_Creatable = False
Attribute VB_PredeclaredId = True
Attribute VB_Exposed = False
Attribute VB_TemplateDerived = False
Attribute VB_Customizable = False
Private Sub ComboBox1_Change()

End Sub

Private Sub CommandButton1_Click()
    
            If UserForm1.OptionButton1.Value = True Then
                Module3.getFenceElements111
            ElseIf UserForm1.OptionButton2.Value = True Then
                Module4.getFenceElements
            ElseIf UserForm1.OptionButton3.Value = True Then
                Module5.placecell
            ElseIf UserForm1.OptionButton4.Value = True Then
        MsgBox ("d")
            Else: Module1.sublist
            End If

End Sub

Private Sub CommandButton2_Click()

End Sub

Private Sub OptionButton1_Click()

End Sub

Private Sub OptionButton4_Click()

End Sub

Private Sub UserForm_Click()

End Sub
