Attribute VB_Name = "Module1"
Sub HelloWorld()

'Dim myex As Excel.Application
'Dim mywb As Excel.Workbook
'Dim mysht As Worksheet
'
'Set myex = New Excel.Application
'myex.Visible = True
'Set mywb = myex.Workbooks.Open("C:\Users\lenovo\Downloads\111.xlsx")
'Set mysht = mywb.Worksheets(1)
'MsgBox mysht.Name




Dim objDF As MicroStationDGN.DesignFile
Dim oscan As ElementScanCriteria
Dim oenum As ElementEnumerator
Dim olevels As Levels
Dim olevel As Level
Dim ele As Element


Dim myexcel As excel.Application
Dim mywb As excel.Workbook
Dim myws As excel.Worksheet
Dim i As Integer
Dim dic As New Dictionary


i = 1

Set myexcel = New excel.Application
Set mywb = myexcel.Workbooks.Open("D:\1111\sun.xlsx")
myexcel.Visible = True
Set myws = mywb.Worksheets(1)




Set objDF = MicroStationDGN.ActiveDesignFile
Set olevels = ActiveModelReference.Levels
Set oscan = New ElementScanCriteria

oscan.ExcludeAllTypes
oscan.IncludeType msdElementTypeCellHeader

Debug.Print olevels.Count
Set oenum = ActiveModelReference.Scan(oscan)

'CadInputQueue.SendCommand "Mark"
ShowStatus "sunrenlong"
Do While oenum.MoveNext
    
    Set ele = oenum.Current
    Set olevel = ActiveModelReference.Levels(1)
    If ele.IsCellElement Then
      Debug.Print ele.AsCellElement.Name
            If Not dic.Exists(ele.AsCellElement.Name) Then
                   dic.Add ele.AsCellElement.Name, 1
                
            ElseIf dic.Exists(ele.AsCellElement.Name) Then
                   dic.Item(ele.AsCellElement.Name) = dic.Item(ele.AsCellElement.Name) + 1
                   'MsgBox dic.Item("Robot_KR210 R2700 extra")
            End If
            Debug.Print dic.Item(ele.AsCellElement.Name)
                
          
          
          
'      myws.Cells(i, 1).Value = ele.AsCellElement.Name
'      i = i + 1
      
'      If InStr(ele.AsCellElement.Name, "Robot_KR210 R2700 extra") Then
'      ele.Level = ActiveModelReference.Levels("电控柜及桥架")
'
'      ele.Color = 3
'      ele.Redraw
'      ele.Rewrite
'
'      End If
    End If
    
Loop
    

Dim a


For Each a In dic.Keys
    myws.Cells(i, 1).Value = a
    myws.Cells(i, 2).Value = dic(a)
    i = i + 1

Next

'myws.Columns.AutoFit
myws.Range("A:A").AutoFit


End Sub



Sub sublist()




Dim objDF As MicroStationDGN.DesignFile
Dim oscan As ElementScanCriteria
Dim oenum As ElementEnumerator
Dim olevels As Levels
Dim olevel As Level
Dim ele As Element


Dim myexcel As excel.Application
Dim mywb As excel.Workbook
Dim myws As excel.Worksheet
Dim i As Integer
i = 1
Dim dic As New Dictionary


Set myexcel = New excel.Application
Set mywb = myexcel.Workbooks.Open("D:\1111\sun.xlsx")
myexcel.Visible = True
Set myws = mywb.Worksheets(1)




Set objDF = MicroStationDGN.ActiveDesignFile
Set olevels = ActiveModelReference.Levels
Set oscan = New ElementScanCriteria

oscan.ExcludeAllTypes
oscan.IncludeType msdElementTypeCellHeader

Debug.Print olevels.Count
Set oenum = ActiveModelReference.Scan(oscan)

ShowStatus "sunrenlong"
Do While oenum.MoveNext

    Set ele = oenum.Current
    Set olevel = ActiveModelReference.Levels(1)
    If ele.IsCellElement Then
      Debug.Print ele.AsCellElement.Name
            If Not dic.Exists(ele.AsCellElement.Name) Then
                   dic.Add ele.AsCellElement.Name, 1
                
            ElseIf dic.Exists(ele.AsCellElement.Name) Then
                   dic.Item(ele.AsCellElement.Name) = dic.Item(ele.AsCellElement.Name) + 1
                   'MsgBox dic.Item("Robot_KR210 R2700 extra")
            End If
            Debug.Print dic.Item(ele.AsCellElement.Name)

    End If
    
Loop
    

Dim a


For Each a In dic.Keys
    myws.Cells(i, 1).Value = a
    myws.Cells(i, 2).Value = dic(a)
    i = i + 1

Next

'myws.Columns.AutoFit
myws.Range("A:A").AutoFit


End Sub





End Sub

Attribute VB_Name = "Module2"
' Function for checking the existence of a level
Private Function LevelExist(LevelName As String) As Boolean
    Dim oLv As Level
    LevelExist = False
    For Each oLv In ActiveDesignFile.Levels
        If UCase(oLv.Name) = UCase(LevelName) Then
            LevelExist = True
            Exit Function
        End If
    Next
End Function
 
Sub CleanUp()
    Dim oLv As Level
    Dim neuerLevel As String
    ' Check whether the new name was given as a parameter:
    neuerLevel = KeyinArguments
     
    ' If no parameter is given, use "LevelOfText":
    If Len(Trim(neuerLevel)) = 0 Then
        neuerLevel = "LevelOfText"
    End If
     
    ' If the new level name does not exist, then create the level:
    If Not LevelExist(neuerLevel) Then
        ActiveDesignFile.AddNewLevel neuerLevel
    End If
       
    Set oLv = ActiveDesignFile.Levels(neuerLevel)
    oLv.ElementColor = 1
     
    ' Look for all text and move it to the new level:
    Dim Ee As ElementEnumerator
    Dim Sc As New ElementScanCriteria
    Sc.ExcludeAllTypes
    Sc.IncludeType msdElementTypeCellHeader
    Set Ee = ActiveModelReference.Scan(Sc)
    Do While Ee.MoveNext
'        Set Ee.Current.Level = oLv
'        Debug.Print (Ee.Current.AsCellElement.Name)
        If InStr(Ee.Current.AsCellElement.Name, "210") Then
        Debug.Print (Ee.Current.AsCellElement.Name)
        Ee.Current.AsCellElement.Color = 2
        End If
        Ee.Current.Rewrite
    Loop
    Debug.Print ("ok")
End Sub

Attribute VB_Name = "Module3"
Public Sub getFenceElements()
   Dim oFence As Fence
   Dim oElEnum As ElementEnumerator
   Dim oEl As Element
   Set oFence = ActiveDesignFile.Fence
   If oFence.IsDefined Then
      Set oElEnum = oFence.GetContents
      oElEnum.Reset
      While oElEnum.MoveNext
         Set oEl = oElEnum.Current
         'Change the color of the element
         oEl.Color = 3
         oEl.Redraw msdDrawingModeNormal
         oEl.Rewrite
      Wend
   End If
End Sub


Public Sub getFenceElements111()
   Dim oFence As Fence
   Dim oElEnum As ElementEnumerator
   Dim oEl As Element
   
   
Dim myexcel As excel.Application
Dim mywb As excel.Workbook
Dim myws As excel.Worksheet
Dim i As Integer
Dim dic As New Dictionary
i = 1

Set myexcel = New excel.Application
Set mywb = myexcel.Workbooks.Open("D:\1111\sun.xlsx")
myexcel.Visible = True
Set myws = mywb.Worksheets(1)

   
   
   
   Set oFence = ActiveDesignFile.Fence
   If oFence.IsDefined Then
      Set oElEnum = oFence.GetContents
      oElEnum.Reset
      While oElEnum.MoveNext
      Set ele = oElEnum.Current
                            If ele.IsCellElement Then
                              Debug.Print ele.AsCellElement.Name
                                    If Not dic.Exists(ele.AsCellElement.Name) Then
                                           dic.Add ele.AsCellElement.Name, 1
                                        
                                    ElseIf dic.Exists(ele.AsCellElement.Name) Then
                                           dic.Item(ele.AsCellElement.Name) = dic.Item(ele.AsCellElement.Name) + 1
                                           'MsgBox dic.Item("Robot_KR210 R2700 extra")
                                    End If
                                    Debug.Print dic.Item(ele.AsCellElement.Name)
                        
                            End If
      Wend
   End If
   
   
Dim a


For Each a In dic.Keys
    myws.Cells(i, 1).Value = a
    myws.Cells(i, 2).Value = dic(a)
    i = i + 1
Next

myws.Range("A:A").AutoFit
   
   
   
End Sub

Attribute VB_Name = "Module4"
Public Sub getFenceElements()
   Dim oFence As Fence
   Dim oElEnum As ElementEnumerator
   Dim oEl As Element
   
   
Dim myexcel As excel.Application
Dim mywb As excel.Workbook
Dim myws As excel.Worksheet
Dim i As Integer
Dim dic As New Dictionary
i = 1
'
'Set myexcel = New Excel.Application
'Set mywb = myexcel.Workbooks.Open("D:\1111\sun.xlsx")
'myexcel.Visible = True
'Set myws = mywb.Worksheets(1)

   
   
Set objDF = MicroStationDGN.ActiveDesignFile
Set olevels = ActiveModelReference.Levels
Set oscan = New ElementScanCriteria

oscan.ExcludeAllTypes
oscan.IncludeType msdElementTypeCellHeader


Set oenum = ActiveModelReference.Scan(oscan)

Do While oenum.MoveNext

    Set ele = oenum.Current
    Dim ocell As CellElement
    
    If ele.IsCellElement Then
                Set ocell = ele.AsCellElement
                
            If Not dic.Exists(ocell.Origin.X) Then
                   dic.Add ele.AsCellElement.Name, 1
                   Debug.Print ocell.Origin.X
                
            ElseIf dic.Exists(ocell.Origin.X) Then
                   dic.Item(ele.AsCellElement.Name) = dic.Item(ele.AsCellElement.Name) + 1
                   Debug.Print ocell.Origin.X
            End If
            Debug.Print dic.Item(ele.AsCellElement.Name)

    End If
    
Loop
   
'
'Dim a
'
'
'For Each a In dic.Keys
'    myws.Cells(i, 1).Value = a
'    myws.Cells(i, 2).Value = dic(a)
'    i = i + 1
'Next
'
'myws.Range("A:A").AutoFit
'
   
   
End Sub

Attribute VB_Name = "Module5"
Sub placecell()

Dim ocell As CellElement
Dim myexcel As excel.Application
Dim mywb As excel.Workbook
Dim myws As excel.Worksheet

Set myexcel = GetObject(, "excel.application")
Set mywb = myexcel.ActiveWorkbook
Set myws = mywb.Worksheets(1)
Debug.Print (myws.Name)


Dim lastrow As Integer
lastrow = myws.UsedRange.Rows.Count
Dim a As Double
Dim b As Double
Dim c As String
Dim d As Integer
Dim op As Point3d
Dim orotation As Matrix3d
Dim dangle As Double

op.X = 0
op.Y = 0
op.Z = 1

For i = 2 To lastrow

dangle = (Round(myws.Cells(i, 6).Value, 2)) / 3.14 * Pi
a = CDbl(myws.Cells(i, 2).Value)
b = CDbl(myws.Cells(i, 3).Value)
d = InStr(1, myws.Cells(i, 1).Value, "_____", vbTextCompare) + 5
c = Mid(myws.Cells(i, 1).Value, d)


orotation = Matrix3dFromVectorAndRotationAngle(op, dangle)


'Set ocell = CreateCellElement3("1234", Point3dFromXY(a, b), False)
Set ocell = CreateCellElement2(c, Point3dFromXY(a, b), Point3dFromXYZ(1, 1, 1), True, orotation)
ActiveModelReference.AddElement ocell
ocell.Redraw
ocell.Rewrite
Debug.Print (ocell.Name)
Next




ShowStatus "Over"

End Sub

Attribute VB_Name = "Module6"
Function GetTagSet(strName As String) As TagSet
    Dim oTagSets As TagSets
    
    Set oTagSets = ActiveDesignFile.TagSets
    On Error Resume Next
    Set GetTagSet = oTagSets(strName)
    If GetTagSet Is Nothing Then Set GetTagSet = oTagSets.Add(strName)
End Function

Sub AddTagDefinitions(oTagSet As TagSet)
    Dim oDefs As TagDefinitions
    Dim oTagDef As TagDefinition
    
    Set oDefs = oTagSet.TagDefinitions
    Set oTagDef = oDefs.Add("StringTag", msdTagTypeCharacter)
    
    With oTagDef
        '  Now print out the initial values for the tag definition properties
        Debug.Print "DefaultValue is " & .DefaultValue
        Debug.Print "IsConstant is " & .IsConstant
        Debug.Print "IsHidden is " & .IsHidden
        Debug.Print "Name is " & .Name
        Debug.Print "Prompt is " & .Prompt
        Debug.Print "TagSetName is " & .TagSetName
        Debug.Print "TagType is " & .TagType
        
        .IsConstant = True
        .DefaultValue = "THIS IS A CONSTANT VALUE"
    End With
    
    Set oTagDef = oDefs.Add("DoubleTag", msdTagTypeDouble)
    With oTagDef
        .DefaultValue = 17.5
        .IsConstant = False
        .Prompt = "Enter a double value"
    End With
    Set oTagDef = oDefs.Add("LongTag", msdTagTypeLongInteger)
    With oTagDef
        .DefaultValue = 70000
        .IsConstant = False
        .Prompt = "Enter an integer value"
    End With
End Sub

Sub RemoveAttributeSet(dgn As DesignFile, strName As String)
    On Error Resume Next '  Consume the error if it is not there
    dgn.TagSets.Remove (strName)
End Sub

Sub TagElementWithSet(ele As Element, tset As TagSet)
    Dim index As Integer
    Dim tags() As TagElement
    
    tags = ele.AddTags(tset)
    For index = LBound(tags) To UBound(tags)
        With tags(index)
            .Move Point3dFromXY(0, index + 100)
            .Redraw
            '  AddTags added it to the model.  Rewrite it now
            '  since it has been moved.
            .Rewrite
        End With
    Next
End Sub

Sub DoExample()
    Dim oTagSet As TagSet
    Dim strTagSetName As String
    Dim ele As LineElement
    
    strTagSetName = "VbaExample"
    
    RemoveAttributeSet ActiveDesignFile, strTagSetName
    
    Set oTagSet = GetTagSet(strTagSetName)
    AddTagDefinitions oTagSet
    
    '  Create the element to tag
    Set ele = CreateLineElement2(Nothing, Point3dFromXY(0, 0), Point3dFromXY(100, 0))
    ele.Redraw
    ActiveModelReference.AddElement ele
    
    TagElementWithSet ele, oTagSet
End Sub

Attribute VB_Name = "Module7"
Sub createtext()
Dim otext As TextElement
Dim olocation As Point3d
Dim ocontent As String

    Dim Ee As ElementEnumerator
    Dim Sc As New ElementScanCriteria
    Sc.ExcludeAllTypes
    Sc.IncludeType msdElementTypeCellHeader
    Set Ee = ActiveModelReference.Scan(Sc)
    Do While Ee.MoveNext
        olocation = Ee.Current.AsCellElement.Origin
        ocontent = Ee.Current.AsCellElement.Name

        If UserForm1.OptionButton5.Value = True Then
            ocontent = UserForm1.TextBox1.Text + "_" + ocontent
        End If

        Set otext = CreateTextElement1(Nothing, ocontent, olocation, Matrix3dIdentity)
        otext.TextStyle.Height = 500
        otext.TextStyle.Width = 500
        ActiveModelReference.AddElement otext
        otext.Redraw

    Loop
    Debug.Print ("ok")
    End Sub
'------------------------------------------------------------------

Sub manualselection()
Dim otext2 As TextElement
Dim olocation2 As Point3d
Dim ocontent2 As String


    Dim Ee As ElementEnumerator
    Set Ee = ActiveModelReference.GetSelectedElements
    Do While Ee.MoveNext
        If Ee.Current.Type = msdElementTypeCellHeader Then
            olocation2 = Ee.Current.AsCellElement.Origin
            ocontent2 = Ee.Current.AsCellElement.Name
            
            If UserForm1.OptionButton5.Value = True Then
                ocontent2 = UserForm1.TextBox1.Text + "_" + ocontent2
            End If
                   
            Set otext2 = CreateTextElement1(Nothing, ocontent2, olocation2, Matrix3dIdentity)
            otext2.TextStyle.Height = 500
            otext2.TextStyle.Width = 500
            ActiveModelReference.AddElement otext2
            otext2.Redraw
        End If
    Loop
    Debug.Print ("ok")


End Sub

Attribute VB_Name = "Module8"
Sub CreateAtLevel()
    Dim oNewElement As Element
    Dim points(1) As Point3d
    Dim oSaveLevel As Level

    ' Initialize the points of the line
    With points(0)
        .X = 0.682
        .Y = -0.43
    End With
    With points(1)
        .X = -0.12
        .Y = -0.53
    End With

    '  The line gets active level when it is created. Then this code
    '  immediately changes the level.  Then it adds the element
    '  to the current model. Finally it displays the level.
    '
    Set oNewElement = CreateLineElement1(Nothing, points)
    Set oNewElement.Level = ActiveDesignFile.Levels.FindByCode(10)
    ActiveModelReference.AddElement oNewElement
    oNewElement.Redraw

    '  The next element will be one master unit above
    '  the previous unit.
    '
    points(0).Y = points(0).Y + 1

    '  This time, set the element's level by changing the active level
    '  prior to creating the element.
    '
    Set oSaveLevel = ActiveSettings.Level
    ActiveSettings.Level = ActiveDesignFile.Levels.FindByCode(1)

    Set oNewElement = CreateTextElement1(Nothing, "ON LEVEL 15", points(0), Matrix3dIdentity)
    ActiveModelReference.AddElement oNewElement
    oNewElement.Redraw

    ActiveSettings.Level = oSaveLevel

End Sub

Attribute VB_Name = "UserForm1"
Attribute VB_Base = "0{152E51D9-D5E0-436E-9EE7-5C0F1FA588E8}{CA232F1B-DFC5-4E41-8B0C-9217D7E6E3F0}"
Attribute VB_GlobalNameSpace = False
Attribute VB_Creatable = False
Attribute VB_PredeclaredId = True
Attribute VB_Exposed = False
Attribute VB_TemplateDerived = False
Attribute VB_Customizable = False
Private Sub ComboBox1_Change()

End Sub

Private Sub CommandButton1_Click()
    
            If UserForm1.OptionButton1.Value = True Then
                Module3.getFenceElements111
            ElseIf UserForm1.OptionButton2.Value = True Then
                Module4.getFenceElements
            ElseIf UserForm1.OptionButton3.Value = True Then
                Module5.placecell
            ElseIf UserForm1.OptionButton4.Value = True Then
        MsgBox ("d")
            Else: Module1.sublist
            End If

End Sub

Private Sub CommandButton2_Click()
Module2.CleanUp
End Sub

Private Sub CommandButton3_Click()
Module5.placecell
End Sub

Private Sub CommandButton4_Click()
If UserForm1.OptionButton6.Value = True Then
    Module7.manualselection
Else
    Module7.createtext
End If

End Sub

Private Sub Frame2_Click()

End Sub

Private Sub OptionButton1_Click()

End Sub

Private Sub OptionButton4_Click()

End Sub


Private Sub UserForm_Click()

End Sub
